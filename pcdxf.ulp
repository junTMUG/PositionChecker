//
// Export the EAGLE outline and holes to DXF for the Craft-ROBO/Silhouette Cameo cutting plotter.
//
// Copyright (c) 2010 SWITCHSCIENCE, Inc.
// Copyright (c) 2012 Yoshihiro TSUBOI
// Copyright (c) 2012 CAP, INC.
//
// Type "run pcdxf" in the board editor window.
//

// Configuration

string HEADER =
"  0\n"
"SECTION\n"
"  2\n"
"HEADER\n"
"  9\n"
"$ACADVER\n"
"  1\n"
"AC1009\n"
"  9\n"
"$MEASUREMENT\n"
" 70\n"
"  1\n"				// unit: mm
"  0\n"
"ENDSEC\n"
"  0\n"
"SECTION\n"
"  2\n"
"ENTITIES\n";

string LINE =
"  0\n"
"LINE\n"
"  8\n"
"  0\n"					// layer
" 10\n"
"%f\n"					// start x
" 20\n"
"%f\n"					// start y
" 11\n"
"%f\n"					// end x
" 21\n"
"%f\n";					// end y

string CIRCLE =
"  0\n"
"CIRCLE\n"
"  8\n"
"  0\n"					// layer
" 10\n"
"%f\n"					// center x
" 20\n"
"%f\n"					// center y
" 40\n"
"%f\n";					// radius

string TRAILER =
"  0\n"
"ENDSEC\n"
"  0\n"
"EOF\n";

int
processBoard(UL_BOARD B) {
  int count = 0;
  printf("%s", HEADER);
  B.elements(E) {
    E.package.contacts(C) {
      if (C.smd) continue;
      
      real x = C.pad.x / 10000.0;
      real y = C.pad.y / 10000.0;
      real d = C.pad.drill / 20000.0;
      
      printf(CIRCLE, x, y, d);
      count++;
    }
    
    E.package.holes(H) {
      real x = H.x / 10000.0;
      real y = H.y / 10000.0;
      real d = H.drill / 20000.0;

      printf(CIRCLE, x, y, d);
      count++;
    }
  }

  B.holes(H) {
    real x = H.x / 10000.0;
    real y = H.y / 10000.0;
    real d = H.drill / 20000.0;

    printf(CIRCLE, x, y, d);
    count++;
  }

  B.wires(W) {
    if (W.layer != LAYER_DIMENSION) continue;

    real sx = W.x1 / 10000.0;
    real sy = W.y1 / 10000.0;
    real ex = W.x2 / 10000.0;
    real ey = W.y2 / 10000.0;
    printf(LINE, sx, sy, ex, ey);
    count++;
  }

  printf("%s", TRAILER);
  return count;
}

board(B) {
  int t;
  output(filesetext(B.name, "-holes.dxf")) t = processBoard(B);

  string message;
  sprintf(message, ";DXF files generated with %d objects", t);	// ';' for information
  dlgMessageBox(message);
}
